Option Explicit
'Script written by <insert name>
'Script copyrighted by <insert company name>
'Script version 26 July 2013 15:35:57

Call Main()
Sub Main()
	
	Dim curveIn
	Dim curveArea(), randomColor, curveBool(), surf
	Dim countPanel, panelNum, intIndex
	Dim i, j
	
	curveIn = Rhino.GetObjects("select curves", 4)
	
	ReDim curveArea(UBound(curveIn))
	ReDim curveBool(UBound(curveIn))
	
	For i = 0 To UBound(curveIn)
		
		curveArea(i) = Round(Rhino.CurveArea(curveIn(i))(0), 3)
		curveBool(i) = False
		
	Next
	
	countPanel = 0
	panelNum = 0
	
	For i = 0 To UBound(curveIn)
		
		randomColor = RGB(Rnd * 255, Rnd * 255, Rnd * 255)

		If curveBool(i) = False Then
			
			intIndex = countPanel
			Rhino.MaterialColor intIndex, randomColor
			curveBool(i) = True
			'Rhino.ObjectColor curveIn(i), randomColor
			surf = Rhino.AddPlanarSrf(curveIn(i))				
			Rhino.ObjectColor surf, randomColor
			countPanel = countPanel + 1
			
			intIndex = Rhino.AddMaterialToObject(surf(0))
			
			For j = 0 To UBound(curveIn)
			
				If curveArea(i) = curveArea(j) And curveBool(j) = False Then
					
					curveBool(j) = True
					'Rhino.ObjectColor curveIn(j), randomColor
					surf = Rhino.AddPlanarSrf(curveIn(j))				
					Rhino.ObjectColor surf, randomColor
					intIndex = Rhino.AddMaterialToObject(surf(0))
					
				End If
			
			Next
			
		End If
	
	Next
	
	Rhino.Print(countPanel & " different glass panel types")
	Rhino.Print(UBound(curveIn) & " total panels")
	
End Sub
